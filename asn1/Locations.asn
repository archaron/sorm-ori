Locations DEFINITIONS IMPLICIT TAGS ::=
BEGIN

EXPORTS LocationInfo;

IMPORTS ProjectionType
    FROM NetworkIdentifiers;

MobileORILocation ::= SEQUENCE {
  mcc [0]  UTF8String (SIZE (1 .. 4)) OPTIONAL,             --- код страны оператора связи пользователя ОРИ
  mnc [1]  UTF8String (SIZE (1 .. 3)) OPTIONAL,             --- код оператора связи пользователя ОРИ
  lac [2]  INTEGER (0 .. 65535) OPTIONAL,                   --- код LAC оператора связи пользователя ОРИ
  cell [3] INTEGER (0 .. 4294967295) OPTIONAL,              --- код БС оператора связи пользователя ОРИ
  network-operator [4] UTF8String (SIZE (1 .. 64)) OPTIONAL --- наименование оператора связи пользователя ОРИ
}

GeoLocation ::= SEQUENCE {
  latitude-grade REAL,              --- широта
  longitude-grade REAL,             --- долгота
  projection-type ProjectionType    --- тип проекции координат
}

LocationInfo ::= SEQUENCE {
  mobile-ori-location [0] MobileORILocation OPTIONAL,
  geo-location [1]        GeoLocation OPTIONAL,
  description [2]         UTF8String (SIZE (1 .. 4096)) OPTIONAL
}

END
